FME workspace surdimensionnement.fmw

Parameters:
- DestDataset_SHAPE = L:\Chardonnens Bastien\PROJET\SURDIMENSIONNEMENT\DATA\SHAPE   # Destination Esri Shape Folder
- SourceDataset_SHAPE = L:\Chardonnens Bastien\PROJET\SURDIMENSIONNEMENT\DATA\SHAPE\SAMPLE\regbl.shp   # Source Esri Shape File(s)
- SourceDataset_SHAPE_9 = L:\Chardonnens Bastien\PROJET\SURDIMENSIONNEMENT\DATA\SHAPE\SAMPLE\batiment_h.shp   # Source Esri Shape File(s)
- SourceDataset_SHAPE_7 = L:\Chardonnens Bastien\PROJET\SURDIMENSIONNEMENT\DATA\SHAPE\SAMPLE\bien_fonds.shp   # Source Esri Shape File(s)
- SourceDataset_SHAPE_11 = L:\Chardonnens Bastien\PROJET\SURDIMENSIONNEMENT\DATA\SHAPE\SAMPLE\affectation_com.shp   # Source Esri Shape File(s)
- SourceDataset_SHAPE_8 = L:\Chardonnens Bastien\PROJET\SURDIMENSIONNEMENT\DATA\SHAPE\SAMPLE\commune.shp   # Source Esri Shape File(s)
- SourceDataset_SHAPE_10 = L:\Chardonnens Bastien\PROJET\SURDIMENSIONNEMENT\DATA\SHAPE\SAMPLE\couverture_sol.shp   # Source Esri Shape File(s)

Readers:
- SHAPE_2: SHAPE from $(SourceDataset_SHAPE) in CH1903.LV03_swisstopo
- SHAPE_3: SHAPE from $(SourceDataset_SHAPE_9) in CH1903.LV03_swisstopo
- SHAPE_4: SHAPE from $(SourceDataset_SHAPE_7) in CH1903.LV03_swisstopo
- SHAPE_6: SHAPE from $(SourceDataset_SHAPE_11) in CH1903.LV03_swisstopo
- SHAPE_5: SHAPE from $(SourceDataset_SHAPE_8) in CH1903.LV03_swisstopo
- SHAPE_1: SHAPE from $(SourceDataset_SHAPE_10) in CH1903.LV03_swisstopo

Writers:
- SHAPE_7: SHAPE to $(DestDataset_SHAPE) in CH1903.LV03_swisstopo

batiment_h (reader SHAPE_3)
    attributes: OBJECTID_1 number(9,0), OBJECTID_2 number(9,0), OBJECTID number(19,11), QUALITY number(19,11), TYPE number(19,11), REGBL_EGID number(19,11), STATE_OF date, FOSNR number(19,11), CH_GEN number(19,11), CH_DESCR_F char(50), CH_DESCR_G char(50), FR_GEN number(19,11), CODE_CSOL_ number(19,11), FR_DESCR char(50), GE_DESCR char(50), LOT_ETAT number(19,11), LOT_ETAT_F char(30), ID_DM char(100), SOURCE char(100), FID_LCSURF char(232), AREA_BAT number(19,11), BUILDINGNU char(20), COUNT number(9,0), MIN number(13,11), MAX number(13,11), RANGE number(13,11), MEAN number(13,11), STD number(13,11), SUM number(13,11), Shape_Leng number(19,11),
      Shape_Area number(19,11), MEAN_robus number(13,11)
    -> CenterPointReplacer
CenterPointReplacer
    CENTERPOINT -> TestFilter_2
TestFilter_2
    DEFAULT_VALUE = <UNFILTERED>
    TEST_LIST:
      BOOL_OP,AND,COMPOSITE_TEST,<Unused>,TEST_CLAUSE,"TEST @Value(MEAN_robus) = 0
      TEST @Value(Shape_Area) > 25",@Value(MEAN_robus) = 0
    @Value(MEAN_robus) = 0 -> Deaggregator_2
Deaggregator_2
    GEOM_NAME_FIELD = _geometry_name
    PART_NUMBER_FIELD = _part_number
    ID_ATTR = _hierarchy_id
    COPY_ATTR = Every Node
    SPLIT_COMPOSITES = No
    LIST_ATTR_MODE_LOOKUP = LEAN
    MODE = Flatten One Level
    PARENT_ID_ATTR = _hierarchy_parent_id
    EXPLODE_INSTANCES = No
    ID_SELECTION = ID and Parent ID
    CHILD_ID_ATTR = _hierarchy_child_id_list
    DEAGGREGATED -> SpatialFilter [input 1]
regbl (reader SHAPE_2)
    attributes: EGID number(10,0), EPROID char(1), GESTNR char(1), GBABID char(1), GBAGID number(6,0), GDENR number(5,0), GEGRID char(15), GGBKR number(2,0), GPARZ number(6,0), GEBNR char(1), GBEZ char(22), GANZDOM number(2,0), GKODE number(11,3), GKODN number(11,3), GKODX number(19,15), GKODY number(19,15), GKSCE_ number(4,0), GLOC1 number(3,0), GLOC2 number(3,0), GLOC3 char(1), GLOC4 char(1), GSTAT_ number(5,0), GKAT_ number(5,0), GKLAS_ number(5,0), GBAUJ number(5,0), GBAUP_ number(5,0), GRENJ number(5,0), GRENP_ number(5,0), GABBJ char(1), GAREA number(5,0),
      GASTW number(3,0), GAZZI number(4,0), GANZWHG number(4,0), GHEIZ_ number(5,0), GENHZ_ number(5,0), GWWV__ number(2,0), GENWW_ number(5,0), GADOM number(2,0), GAWHG number(2,0), GKPLAUS number(4,0), GWHGSTD_ number(4,0), GWHGVER__ number(2,0), GPLAUS_ number(4,0), GBAUM number(7,4), GRENM char(1), GABBM char(1), GMUTDAT char(11), GEXPDAT char(11)
    -> TestFilter_3
TestFilter_3
    DEFAULT_VALUE = <UNFILTERED>
    TEST_LIST = BOOL_OP,OR,COMPOSITE_TEST,<Unused>,TEST_CLAUSE,"TEST @Value(GBAUJ) > 2001",@Value(GBAUJ) > 2001
    @Value(GBAUJ) > 2001 -> Deaggregator_3
Deaggregator_3
    GEOM_NAME_FIELD = _geometry_name
    PART_NUMBER_FIELD = _part_number
    ID_ATTR = _hierarchy_id
    COPY_ATTR = Every Node
    SPLIT_COMPOSITES = No
    LIST_ATTR_MODE_LOOKUP = LEAN
    MODE = Flatten One Level
    PARENT_ID_ATTR = _hierarchy_parent_id
    EXPLODE_INSTANCES = No
    ID_SELECTION = ID and Parent ID
    CHILD_ID_ATTR = _hierarchy_child_id_list
    DEAGGREGATED -> SpatialFilter [input 1]
bien_fonds (reader SHAPE_4)
    attributes: OBJECTID number(9,0), IDENTND char(12), NUMBER_MOP char(15), EGRIS_EGRI char(14), COMPLETENE number(4,0), AREA_MOP number(19,11), STATE_OF date, FOSNR number(9,0), FOSNAME char(40), PARTFOSNAM char(40), NUMBER_MDS char(15), REAL_ESTAT char(15), TOTAL_AREA number(19,11), ABREV_RF char(10), LOT_ETAT number(4,0), ID_DM char(100), SOURCE char(100), FID_IM char(232), FID_BF char(232), RF_LINK_FR char(110), RF_LINK_GE char(110), LOT_ETAT_F char(30), IDENTND_NU char(30), SHAPE_Leng number(19,11), SHAPE_Area number(19,11)
    -> Clipper_2 [input 1]
affectation_com (reader SHAPE_6)
    attributes: OBJECTID number(9,0), NUFECO number(9,0), ZONE char(10), NOSECT number(4,0), LIEU char(50), ZPAD char(3), AMEDIF char(3), PLANAFF char(3), DATPLAN date, REMARQ char(200), OPERAT char(20), DATSAI date, ZPED char(3), NUREGPAD number(4,0), ETAT_PAD char(1), SURF_SECT number(9,0), TYPSTD char(6), NUFECO_ZON char(11), SENSIBLESP number(4,0), TYPPROT char(10), DEROGATION number(4,0), Shape_Leng number(19,11), Shape_Area number(19,11)
    -> Tester_2
Tester_2
    TEST_MODE = Automatic
    TEST_DESCRIPTION = ""
    BOOL_OP = OR
    TEST_CLAUSE:
      TEST @Value(TYPSTD) = ZRFD
      TEST @Value(TYPSTD) = ZRMD
      TEST @Value(TYPSTD) = ZRHD
      TEST @Value(TYPSTD) = ZM
      TEST @Value(TYPSTD) = ZV
    PASSED -> Clipper_2 [input 2]
Clipper_2
    CLIP_TYPE = Multiple Clippers
    PRESERVE_CLIPPEE_EXTENTS = No
    ATTR_CONFLICT_RES = Use Clippee
    ATTR_ACCUM_MODE = Merge Clipper
    CREATE_AGGREGATES = Yes
    CLIPPED_ATTR = _clipped
    BOUNDARY_CASES = Treat as Inside
    INSIDE -> AttributeKeeper
AttributeKeeper
    KEEP_ATTRS = TYPSTD
    -> Clipper_3 [input 2]
commune (reader SHAPE_5)
    attributes: OBJECTID number(19,10), JOIN_COUNT number(19,10), TARGET_FID number(19,10), CAD8102S_C char(30), FOSNR number(19,10), COMPLET__D date, COMMUNE_20 number(19,10), SUM_SR15 number(19,10), SUM_SRL number(19,10), FRENCH_NAM char(50), GERMAN_NAM char(50), SHAPE_LENG number(19,10), SHAPE_AREA number(19,10), SR15 number(19,10), SRL number(19,10), RATIO number(19,10)
    -> AttributeRenamer
AttributeRenamer
    ATTR_LIST = CAD8102S_1,FOSNR,
    -> Clipper_3 [input 1]
Clipper_3
    CLIP_TYPE = Multiple Clippers
    PRESERVE_CLIPPEE_EXTENTS = No
    ATTR_CONFLICT_RES = Use Clippee
    ATTR_ACCUM_MODE = Merge Clipper
    CREATE_AGGREGATES = Yes
    CLIPPED_ATTR = _clipped
    BOUNDARY_CASES = Treat as Inside
    INSIDE -> Deaggregator
Note: Multipolygone to polygone (spatial filter ne supporte pas les multi)
Deaggregator
    GEOM_NAME_FIELD = _geometry_name
    PART_NUMBER_FIELD = _part_number
    SPLIT_COMPOSITES = Yes
    LIST_ATTR_MODE_LOOKUP = LEAN
    MODE = Flatten One Level
    EXPLODE_INSTANCES = Yes
    DEAGGREGATED -> AreaCalculator_2
AreaCalculator_2
    MULT = 1
    AREA_TYPE = Plane Area
    AREA_ATTR = _area
    -> Tester
Tester
    TEST_MODE = Automatic
    TEST_DESCRIPTION = ""
    BOOL_OP = OR
    TEST_CLAUSE = TEST @Value(_area) > 1
    PASSED -> SpatialFilter [input 2]
Note: Vérifie quelles parcelles contiennent des bâtiments et quelles parcelles n'en contiennent pas
SpatialFilter
    BASE_TYPE = Multiple Filters
    PREDATTR = _predicate
    USE_BOUNDING_BOX = No
    PREDICATE_VALUE = Touches
    PASS_CRITERIA = Pass Against One Filter
    MERGE_ATTRS = No
    CURVE_BOUNDARY_RULE_PARAM = Default Rule
    FAILED -> AttributeKeeper_2
    PASSED -> SR15 (writer SHAPE_7)
SR15 (writer SHAPE_7)
    attributes: OBJECTID number(19,11), JOIN_COUNT number(19,10), TARGET_FID number(19,10), CAD8102S_C char(30), FOSNR number(19,11), COMPLET__D date, COMMUNE_20 number(19,10), SUM_SR15 number(19,10), SUM_SRL number(19,10), FRENCH_NAM char(50), GERMAN_NAM char(50), SHAPE_LENG number(19,10), SHAPE_AREA number(19,10), SR15 number(19,10), SRL number(19,10), RATIO number(19,10), TYPSTD char(6), _clipped char(200), _geometry_ char(200), _part_numb char(200), _area char(200), _predicate char(200)
AttributeKeeper_2
    KEEP_ATTRS = FOSNR,TYPSTD
    -> AreaCalculator
AreaCalculator
    MULT = 1
    AREA_TYPE = Plane Area
    AREA_ATTR = _area
    -> Clipper [input 2]
TimeStamper
    FMT = FME Date/Time (^Y)
    TIME_ATTR = _timestamp
couverture_sol (reader SHAPE_1) [off]
    attributes: QUALITY number(5,0), TYPE number(5,0), REGBL_EGID number(10,0), STATE_OF date, FOSNR number(5,0), CH_GEN number(5,0), CH_DESCR_F char(50), CH_DESCR_G char(50), FR_GEN number(5,0), CODE_CSOL_ number(5,0), FR_DESCR char(50), GE_DESCR char(50), LOT_ETAT number(5,0), LOT_ETAT_F char(30), ID_DM char(100), SOURCE char(100), FID_LCSURF char(232), SHAPE_area number(19,11), SHAPE_len number(19,11)
    -> AttributeKeeper_3
AttributeKeeper_3
    KEEP_ATTRS = FOSNR,FR_GEN,TYPE
    -> TestFilter_4
    -> TestFilter_6
TestFilter_4
    DEFAULT_VALUE = <UNFILTERED>
    TEST_LIST:
      BOOL_OP,OR,COMPOSITE_TEST,<Unused>,TEST_CLAUSE,"TEST @Value(TYPE) IN (1,2,7)
      TEST @Value(FR_GEN) IN (13,17,102,129,130,147)",@Value(TYPE) IN (1,2,7,8,11)
    @Value(TYPE) IN (1,2,7,8,11) -> Clipper [input 1] [off]
Note: Parcelles non construites
Clipper
    CLIP_TYPE = Multiple Clippers
    PRESERVE_CLIPPEE_EXTENTS = No
    ATTR_CONFLICT_RES = Use Clippee
    ATTR_ACCUM_MODE = Merge Clipper
    CREATE_AGGREGATES = Yes
    CLIPPED_ATTR = _clipped
    BOUNDARY_CASES = Treat as Inside
TestFilter_6
    DEFAULT_VALUE = <UNFILTERED>
    TEST_LIST = BOOL_OP,OR,COMPOSITE_TEST,<Unused>,TEST_CLAUSE,"TEST @Value(TYPE) = 8",@Value(TYPE) = 8
Intersector_3
    PERFORM_SELF_INTERSECTION = No
    SEPARATE_COLLINEAR_SEGMENTS = No
    SEG_ATTR = _segments
    DUPLICATE_Z_NODES = No
    OV_ATTR = _overlaps
